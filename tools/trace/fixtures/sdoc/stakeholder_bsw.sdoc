[DOCUMENT]
TITLE: Synthetic stakeholder and BSW requirements (tools/trace fixture)
OPTIONS:
  VIEW_STYLE: Table

[GRAMMAR]
IMPORT_FROM_FILE: @nextbsw

[STK]
UID: STK-001
TITLE: Safety element out of context
STATEMENT: The base software shall be usable as a safety element out of context.
KIND: functional
SOURCE: synthetic
STATUS: partial

[BSR]
UID: BSR-SAFE-001
TITLE: Central safe supervisor
STATEMENT: The base software shall provide one safe supervisor.
KIND: functional
CATEGORY: safety
STATUS: implemented
VERIFICATION: test
SOURCE: synthetic
RELATIONS:
- TYPE: Parent
  VALUE: STK-001
